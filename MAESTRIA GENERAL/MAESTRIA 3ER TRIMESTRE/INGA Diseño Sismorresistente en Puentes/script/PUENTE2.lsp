; Puente de tres tramos - elevacion lateral esquematica
; Unidades: metros. AutoCAD / AutoCAD LT con soporte AutoLISP.
; Uso: APPLOAD -> seleccionar este archivo -> comando PUENTE75
; Nota: geometria vertical esquematica, ya que la imagen no indica alturas.

(defun p75:layer (name color)
  (if (not (tblsearch "LAYER" name))
    (entmake (list '(0 . "LAYER") '(100 . "AcDbSymbolTableRecord")
                   '(100 . "AcDbLayerTableRecord") (cons 2 name)
                   '(70 . 0) (cons 62 color) (cons 6 "Continuous")))
  )
)
(defun p75:line (a b lay)
  (entmake (list '(0 . "LINE") '(100 . "AcDbEntity") (cons 8 lay)
                 '(100 . "AcDbLine") (cons 10 (list (car a) (cadr a) 0.0))
                 (cons 11 (list (car b) (cadr b) 0.0)))
  )
)
(defun p75:pl (pts lay closed)
  (entmake
    (append
      (list '(0 . "LWPOLYLINE") '(100 . "AcDbEntity") (cons 8 lay)
            '(100 . "AcDbPolyline") (cons 90 (length pts))
            (cons 70 (if closed 1 0)))
      (mapcar '(lambda (pt) (cons 10 pt)) pts)
    )
  )
)
(defun p75:rect (x1 y1 x2 y2 lay)
  (p75:pl (list (list x1 y1) (list x2 y1) (list x2 y2) (list x1 y2)) lay T)
)
(defun p75:text (pt h s lay)
  (entmake (list '(0 . "TEXT") '(100 . "AcDbEntity") (cons 8 lay)
                 '(100 . "AcDbText") (cons 10 (list (car pt) (cadr pt) 0.0))
                 (cons 40 h) (cons 1 s) '(50 . 0.0)
                 '(7 . "Standard") '(72 . 0) '(73 . 0)))
)
(defun p75:dim (x1 x2 y label)
  (p75:line (list x1 y) (list x2 y) "COTAS")
  (p75:line (list x1 (- y 0.35)) (list x1 (+ y 0.35)) "COTAS")
  (p75:line (list x2 (- y 0.35)) (list x2 (+ y 0.35)) "COTAS")
  ; Flechas simples
  (p75:pl (list (list x1 y) (list (+ x1 0.8) (+ y 0.22)) (list (+ x1 0.8) (- y 0.22))) "COTAS" T)
  (p75:pl (list (list x2 y) (list (- x2 0.8) (+ y 0.22)) (list (- x2 0.8) (- y 0.22))) "COTAS" T)
  (p75:text (list (/ (+ x1 x2) 2.0) (+ y 0.45)) 0.8 label "TEXTOS")
)
(defun c:PUENTE75 (/ oldos)
  (setq oldos (getvar "OSMODE"))
  (setvar "OSMODE" 0)
  (setvar "INSUNITS" 6)
  (p75:layer "TABLERO" 7)
  (p75:layer "PILAS" 3)
  (p75:layer "ESTRIBOS" 2)
  (p75:layer "TERRENO" 8)
  (p75:layer "AGUA" 4)
  (p75:layer "COTAS" 1)
  (p75:layer "TEXTOS" 7)
  (p75:layer "DETALLES" 6)

  ; TABLERO: longitud total 75 m, entre x=0 y x=75
  (p75:rect 0.0 10.0 75.0 11.2 "TABLERO")
  (p75:line (list 0 10.6) (list 75 10.6) "DETALLES")
  ; Barandal esquematico
  (p75:line (list 0 11.35) (list 75 11.35) "DETALLES")
  (p75:line (list 0 11.2) (list 0 11.35) "DETALLES")
  (p75:line (list 75 11.2) (list 75 11.35) "DETALLES")
  (setq x 1.0)
  (while (< x 75.0)
    (p75:line (list x 11.2) (list x 11.35) "DETALLES")
    (setq x (+ x 2.0))
  )

  ; Estribos laterales (esquematicos)
  (p75:pl (list (list -1.8 3.0) (list 1.8 3.0) (list 1.8 9.7)
                 (list 0.8 9.7) (list 0.8 8.6) (list -1.0 8.6)
                 (list -1.0 4.0) (list -1.8 3.0)) "ESTRIBOS" T)
  (p75:pl (list (list 73.2 3.0) (list 76.8 3.0) (list 76.8 4.0)
                 (list 76.0 8.6) (list 74.2 8.6) (list 74.2 9.7)
                 (list 73.2 9.7)) "ESTRIBOS" T)

  ; Pilas en x=22.5 y x=52.5
  (foreach px '(22.5 52.5)
    (p75:rect (- px 1.0) 1.8 (+ px 1.0) 8.9 "PILAS")
    (p75:pl (list (list (- px 1.0) 8.9) (list (- px 1.35) 8.3)
                  (list (- px 1.0) 3.0) (list (- px 1.6) 2.5)
                  (list (+ px 1.6) 2.5) (list (+ px 1.0) 3.0)
                  (list (+ px 1.35) 8.3) (list (+ px 1.0) 8.9))
            "PILAS" T)
    (p75:rect (- px 2.0) 1.4 (+ px 2.0) 1.9 "PILAS")
  )

  ; Terreno y cauce
  (p75:pl (list (list -3.0 2.7) (list 3.0 2.7) (list 6.0 1.0)
                (list 16.0 0.2) (list 22.5 0.0) (list 30.0 -0.3)
                (list 45.0 -0.3) (list 52.5 0.0) (list 60.0 0.2)
                (list 69.0 1.0) (list 72.0 2.7) (list 78.0 2.7))
          "TERRENO" nil)
  ; Agua superficial con pequenas ondas
  (p75:line (list 8.0 1.25) (list 20.5 1.25) "AGUA")
  (p75:line (list 24.5 1.25) (list 50.5 1.25) "AGUA")
  (p75:line (list 54.5 1.25) (list 67.0 1.25) "AGUA")
  (foreach wx '(9 13 17 26 30 34 38 42 46 50 56 60 64)
    (p75:pl (list (list wx 1.25) (list (+ wx 0.7) 1.12)
                  (list (+ wx 1.4) 1.25)) "AGUA" nil)
  )

  ; Cotas principales
  (p75:line (list 0 11.5) (list 0 16.8) "COTAS")
  (p75:line (list 22.5 11.5) (list 22.5 16.8) "COTAS")
  (p75:line (list 52.5 11.5) (list 52.5 16.8) "COTAS")
  (p75:line (list 75 11.5) (list 75 16.8) "COTAS")
  (p75:dim 0 22.5 15.8 "L1 = 22.50 m")
  (p75:dim 22.5 52.5 15.8 "L2 = 30.00 m")
  (p75:dim 52.5 75 15.8 "L3 = 22.50 m")
  (p75:dim 0 75 18.0 "LONGITUD TOTAL = 75.00 m")

  ; Etiquetas
  (p75:text (list 24.0 7.1) 0.8 "PILA 1" "TEXTOS")
  (p75:line (list 23.8 7.3) (list 24.5 7.8) "TEXTOS")
  (p75:text (list 54.0 7.1) 0.8 "PILA 2" "TEXTOS")
  (p75:line (list 53.8 7.3) (list 54.5 7.8) "TEXTOS")
  (p75:text (list -2.4 0.2) 0.7 "ESTRIBO 1" "TEXTOS")
  (p75:text (list 72.0 0.2) 0.7 "ESTRIBO 2" "TEXTOS")
  (p75:text (list 27.0 12.0) 0.65 "ELEVACION LATERAL - PUENTE DE TRES TRAMOS" "TEXTOS")
  (p75:text (list 21.0 -2.0) 0.7 "Esquema ilustrativo; ajustar alturas y detalles con planos de diseno." "TEXTOS")

  (command "_.ZOOM" "_E")
  (setvar "OSMODE" oldos)
  (princ "\nPuente esquematico creado. Unidades en metros. Comando: PUENTE75")
  (princ)
)
(princ "\nArchivo cargado. Escriba PUENTE75 para dibujar el puente.")
(princ)
